module grpc {
    yang-version 1.1;
    namespace "urn:opendaylight:params:xml:ns:yang:grpc";
    prefix "grpc";

    revision "2017-08-30" {
        description "Initial revision of grpc model";
    }

    import ietf-inet-types {
        prefix "inet";
        revision-date 2013-07-15;
    }

    rpc get-notification-stats {
        output {
            leaf drop-count {
                type string;
            }

            leaf publish-count {
                type string;
            }

            leaf cousume-count {
                type string;
            }
        }
    }
}
